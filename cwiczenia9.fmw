FME workspace cwiczenia9.fmw
Startup Python:
      from datetime import datetime
      import smtplib, ssl
      import unicodedata

      port = 465  # For SSL
      smtp_server = "smtp.gmail.com"
      sender_email = "$(email)"  # Enter your address
      receiver_email = "$(email_odbiorcy)"  # Enter receiver address
      district = "$(powiat)"
      #Bez "" string byl czytany do znaku malpy
      password =  "exhdxtpttgvkeleh"   #Hasło wygenerowane w ustawieniach konta
      time = datetime.now().strftime("%H:%M:%S")
      message = "Drogi uzytkowniku $(email_odbiorcy),\no godzinie " + time + " rozpoczeto przetwarzanie danych dla powiatu: $(powiat)."


      context = ssl.create_default_context()
      with smtplib.SMTP_SSL(smtp_server, port, context=context) as server:
          server.login(sender_email, password)
          server.sendmail(sender_email, receiver_email, message)

Parameters:
- email = kamila.ja9@gmail.com   # Podaj email
- haslo =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   # Podaj hasło
- email_odbiorcy = kamila.ja9@gmail.com   # Podaj email klienta
- powiat = lubelski   # Podaj nazwę powiatu
- chmury = 20   # Maksymalne pokrycie chmurami[%]
- data_start = 20220407   # Wprowadź datę początkową(dla NDVI)
- data_koniec = 20221114   # Wprowadź datę końcową(dla NDVI)
- SourceDataset_SHAPEFILE = $(FME_MF_DIR)powiaty\powiaty.shp   # Source Esri Shapefile(s)
- DestDataset_GEOTIFF = D:\AGH\semestr V\BDP roboczy\cw9   # Destination GeoTIFF Folder

Readers:
- SHAPEFILE_1: SHAPEFILE from $(SourceDataset_SHAPEFILE)

Writers:
- GEOTIFF_1: GEOTIFF to $(DestDataset_GEOTIFF) in EPSG:4326

Bookmark: Zadanie 3
powiaty (reader SHAPEFILE_1)
    attributes: gml_id varchar(254), JPT_SJR_KO varchar(254), JPT_POWIER varchar(254), JPT_KOD_JE varchar(254), JPT_NAZWA_ varchar(254), JPT_ORGAN_ varchar(254), JPT_JOR_ID varchar(254), WERSJA_OD varchar(254), WERSJA_DO varchar(254), WAZNY_OD varchar(254), WAZNY_DO varchar(254), JPT_KOD__1 varchar(254), JPT_NAZWA1 varchar(254), JPT_ORGAN1 varchar(254), JPT_WAZNA_ varchar(254), ID_BUFORA_ varchar(254), ID_BUFORA1 varchar(254), ID_TECHNIC varchar(254), IIP_PRZEST varchar(254), IIP_IDENTY varchar(254), IIP_WERSJA varchar(254), JPT_KJ_IIP varchar(254), JPT_KJ_I_1 varchar(254), JPT_KJ_I_2 varchar(254), JPT_OPIS varchar(254), JPT_SPS_KO varchar(254), ID_BUFOR_1 varchar(254), JPT_ID varchar(254), JPT_POWI_1 varchar(254), JPT_KJ_I_3 varchar(254),
      JPT_GEOMET varchar(254), JPT_GEOM_1 varchar(254), SHAPE_LENG varchar(254), SHAPE_AREA varchar(254), REGON varchar(254), RODZAJ varchar(254)
    -> Reprojector
Reprojector
    DEST = EPSG:4326
    INTERPOLATION_TYPE_NAME = Nearest Neighbor
    RASTER_CELL_SIZE = Preserve Cells
    RASTER_TOLERANCE = 0.0
    REPROJECTED -> TestFilter

Bookmark: Zad 4
TestFilter
    DEFAULT_VALUE = <UNFILTERED>
    PASSED_TEST_GROUP_OUTPUT = FIRST
    TEST_LIST = "BOOL_OP,OR,COMPOSITE_TEST,""""""1"""""",TEST_CLAUSE,TEST @Value(JPT_NAZWA_) = powiat $(powiat)",@Value(JPT_NAZWA_) = powiat__powiat_
    @Value(JPT_NAZWA_) = powiat__powiat_ -> SentinelDownloader [Initiator]
    @Value(JPT_NAZWA_) = powiat__powiat_ -> Clipper [CLIPPER]

Bookmark: Zadanie 5
SentinelDownloader
    BEGIN = $(data_start)
    Band_Resolution = 10m
    CloudCover = $(chmury)
    END = $(data_koniec)
    LEVEL = Level 2A
    MOST_RECENT = YES
    key_name = jkami
    key_pw =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
    platform = Sentinel-2
    B04 -> Sampler_B04
    B08 -> Sampler_B08

Bookmark: Zadanie 6/7
Sampler_B04
    RATE = 1
    SAMPLE_MODE = No
    SAMPLE_TYPE_LONG = First N Features
    SAMPLED -> Reprojector_2
    NOT_SAMPLED -> Terminator
Reprojector_2
    DEST = EPSG:4326
    INTERPOLATION_TYPE_NAME = Nearest Neighbor
    RASTER_CELL_SIZE = Preserve Cells
    RASTER_TOLERANCE = 0.0
    REPROJECTED -> NDVICalculator [Red]
Sampler_B08
    RATE = 1
    SAMPLE_MODE = No
    SAMPLE_TYPE_LONG = First N Features
    SAMPLED -> Reprojector_3
    NOT_SAMPLED -> Terminator
Terminator [off]
    MESSAGE = Translation Terminated
Reprojector_3
    DEST = EPSG:4326
    INTERPOLATION_TYPE_NAME = Nearest Neighbor
    RASTER_CELL_SIZE = Preserve Cells
    RASTER_TOLERANCE = 0.0
    REPROJECTED -> NDVICalculator [Infrared]
NDVICalculator
    COLORIZE = Blue-Yellow-Green Palette
    INDEXTYPE = NDVI
    SAVIADJUSTMENT = 0.5
    -> Clipper [CANDIDATE]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> powiaty_NDVI_tiff (writer GEOTIFF_1)
    INSIDE -> RasterStatisticsCalculator
powiaty_NDVI_tiff (writer GEOTIFF_1)
    attributes: gml_id char(254), JPT_SJR_KO char(254), JPT_POWIER char(254), JPT_KOD_JE char(254), JPT_NAZWA_ char(254), JPT_ORGAN_ char(254), JPT_JOR_ID char(254), WERSJA_OD char(254), WERSJA_DO char(254), WAZNY_OD char(254), WAZNY_DO char(254), JPT_KOD__1 char(254), JPT_NAZWA1 char(254), JPT_ORGAN1 char(254), JPT_WAZNA_ char(254), ID_BUFORA_ char(254), ID_BUFORA1 char(254), ID_TECHNIC char(254), IIP_PRZEST char(254), IIP_IDENTY char(254), IIP_WERSJA char(254), JPT_KJ_IIP char(254), JPT_KJ_I_1 char(254), JPT_KJ_I_2 char(254), JPT_OPIS char(254), JPT_SPS_KO char(254), ID_BUFOR_1 char(254), JPT_ID char(254), JPT_POWI_1 char(254), JPT_KJ_I_3 char(254),
      JPT_GEOMET char(254), JPT_GEOM_1 char(254), SHAPE_LENG char(254), SHAPE_AREA char(254), REGON char(254), RODZAJ char(254)

Bookmark: Zadanie 8
RasterStatisticsCalculator
    RASTER_LEVEL = BAND_ONLY
    RASTER_STATS = "0   MEAN   STDEV  "
    -> RasterStatisticsCalculator_Output
    -> Emailer
RasterStatisticsCalculator_Output: Inspector

Bookmark: Zadanie 9
Emailer
    BODY = Proces zakończony powodzeniem
    FROM = $(email)
    SERVICE = Gmail
    SMTP_CONNECTION = GMAIL_NAMED_CONNECTION;kamil Google Gmail (safe.emailer);TIMEOUT;60;FME_CONTROLLER_QUERY_FILE;dependencies/Gmail.fme;FME_CONTROLLER_CHOICE;Gmail
    SUBJECT = Wiadomosc o powodzeniu procesu
    TO = $(email_odbiorcy)
    Sent -> Emailer_Sent
Emailer_Sent: Inspector

FME custom transformer SentinelDownloader
Description 
This transformer allows you to access the COPERNICUS Open Access Hub and download Sentinel-II images right from the source.
Since the existing Sentinel-II reader targets an "Requester pays" Amazon bucket, AWS credentials are required in addition to a charge per x requests or GB.
Using the con terra SentinelDownloader transformer, you only need a free account from COPERNICUS Open Access Hub to access the Sentinel-II data.  
If you have any question or if you are looking for professional services support, please contact fme@conterra.de. 
Configuration 
Input Port 
Initiator: 
An Area Of Interest (AOI) polygon feature OR 
A point feature (e.g. defined in the Creator transformer) OR 
A (textual) WKT representation of a point or polygon feature (e.g. POINT(7.6528 51.9352) )
Coordinates must be in LL84. 
Parameters/Properties 
KEY_NAME:
Please enter your user name from the COPERNICUS Open Access Hub 
KEY_ PW: 
Please enter your account password from the COPERNICUS Open Access Hub 
BEGIN [optional]: 
Choose the start date of your ingestion period 
END [optional]: 
Choose the end date of your ingestion period 
LEVEL: 
Choose between the two data product levels: Level 1C (Top of atmosphere reflectances, geometric and radiometric corrected) and Level 2A (Botton of atmosphere reflectances)
CLOUDCOVER [optional]: 
In this optional parameter, you can choose whether you want your results are filtered by a maximum cloud cover percentage. Keep in mind that this parameter could be the bottleneck of your search query as it possibly will exclude data if the parameter value is too small. 
BAND_RESOLUTION: 
Choose between the three possible spatial resolutions (ground sampling distance) 10m, 20m, 60m, and All. 
Output Ports 
The output depends on the choosen product Level and spatial resolution. For detailed information about a specific band, see this.   
Level 1C: 
10m 
Bands 2, 3, 4, and 8. 
20m 
Bands 5, 6, 7, 8A, 11, and 12. 
60m 
Bands 1, 9, and 10 
All 
All 13 bands at their best posible spatial resolution (see above) and the True Color Image (TCI) 
Level 2A: 
10m 
Bands 2, 3, 4, and 8. 
20m
Bands 2, 3, 4, 5, 6, 7, 8A, 11, and 12 + TCI (all bands in 20m spatial resolution) 
60m 
Bands 1, 2, 3, 4, 5, 6, 7, 8A, 9, 11, and 12 + TCI (all bands in 60m spatial resolution) 
All 
All 12 bands at their best posible spatial resolution (see above) and the True Color Image (TCI)

Parameters:
- platform = Sentinel-2   # Which Platform?
- PARAMETER =   # SciHub credentials (https://scihub.copernicus.eu/dhus/)
- key_name =   # User name
- key_pw =   # Password
- PARAMETER_2 =   # Search parameters
- BEGIN = 20220307   # Enter the start date of ingestion
- END = 20220309   # Enter the end of your ingestion period
- MOST_RECENT = NO   # Latest image?
- LEVEL =   # "Level 1C"%"Level 2A" Product Level
- Band_Resolution =   # Please enter the desired spatial resolution
- CloudCover = 1   # Enter MAX Cloud Cover Percentage in %

Initiator (input)
    -> TextEncoder
Note: Generate API-Key from name:pw and Base64 encoding
Note: Placeholder S1
TextEncoder
    DEST_ATTR = _key_encoded
    ENCODING_TYPE = BASE64_ENCODE
    STRING_TO_ENCODE = $(key_name):$(key_pw)
    -> GeometryFilter
Junction_5
    -> Junction_3
AttributeKeeper
    CREATE_BULK_MODE_FEATURES = NO
    KEEP_ATTRS = _key_encoded,_response_body
    -> XMLFragmenter
Junction_3
    -> Junction_4
Junction_4
    -> Junction_2

Bookmark: Downloading Sentinel-2 data
GeometryFilter
    BREAK_AGG = No
    GEOM_PORT_NAMES = Point Area Text
    POINT -> Reprojector
    AREA -> BoundingBoxReplacer
    TEXT -> AttributeCreator_3
    <UNFILTERED> -> Terminator
Note: Terminate the translation if an unexpected input exists
Terminator
    MESSAGE = Translation Terminated because none of the input parameters was either a point, polygon, or text (WKT) feature.

Bookmark: Spatial filter by point object
Reprojector
    DEST = LL-WGS84
    INTERPOLATION_TYPE_NAME = Nearest Neighbor
    RASTER_CELL_SIZE = Preserve Cells
    RASTER_TOLERANCE = 0.0
    REPROJECTED -> CoordinateExtractor
CoordinateExtractor
    IND = 0
    MODE = Specify Coordinate
    X_ATTR = _x
    Y_ATTR = _y
    Z_ATTR = _z
    -> AttributeCreator
AttributeCreator
    ATTR_TABLE:
      SET_TO date_param = ingestionDate:[@DateTimeFormat($(BEGIN),%Y-%m-%d)T00:00:00.000Z TO @DateTimeFormat($(END),%Y-%m-%d)T23:59:00.000Z]
      SET_TO product_type = FME_CONDITIONAL:DEFAULT_VALUE'producttype:S2MSI2A'BOOL_OP;OR;COMPOSITE_TEST;<Unused>;TEST $(LEVEL) = Level 1C'producttype:S2MSI1C'FME_NUM_CONDITIONS2___
    -> HTTPCaller_3
Note: Select based on intersection with Point and platformname:Sentinel-2 and ingestion date
HTTPCaller_3
    CONNECTION_TIMEOUT_LENGTH = 60
    CUSTOM_HEADERS = Authorization;Basic @Value(_key_encoded)
    ERROR_ATTR = _error
    FOLLOW_REDIRECTS = FOLLOW_WITH_ORIGINAL_METHOD
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://scihub.copernicus.eu/dhus/search?q=(footprint:"Intersects(@Value(_x) @Value(_y))" AND platformname:$(platform) AND @Value(product_type) AND @Value(date_param) AND cloudcoverpercentage:[0 TO $(CloudCover)])&rows=100
    TRANSFER_TIMEOUT_LENGTH = 90
    USE_COOKIES = No
    VERIFY_SSL_CERTIFICATES = Yes
    -> AttributeKeeper
    <REJECTED> -> Junction_5

Bookmark: Spatial filter by Polygon object
BoundingBoxReplacer
    BOXTYPE = 2D Bounding Box
    BOX -> CoordinateExtractor_2
CoordinateExtractor_2
    LIST_NAME = coord
    MODE = All Coordinates
    -> AttributeCreator_2
AttributeCreator_2
    ATTR_TABLE:
      SET_TO date_param = ingestionDate:[@DateTimeFormat($(BEGIN),%Y-%m-%d)T00:00:00.000Z TO @DateTimeFormat($(END),%Y-%m-%d)T23:59:00.000Z]
      SET_TO poly = POLYGON((@Value(coord{0}.x) @Value(coord{0}.y),@Value(coord{1}.x) @Value(coord{1}.y),@Value(coord{2}.x) @Value(coord{2}.y),@Value(coord{3}.x) @Value(coord{3}.y),@Value(coord{4}.x) @Value(coord{4}.y)))
      SET_TO product_type = FME_CONDITIONAL:DEFAULT_VALUE'producttype:S2MSI2A'BOOL_OP;OR;COMPOSITE_TEST;<Unused>;TEST $(LEVEL) = Level 1C'producttype:S2MSI1C'FME_NUM_CONDITIONS2___
    -> HTTPCaller
Note: Select based on intersection with Polygon and platformname:Sentinel-2 and ingestion date
HTTPCaller
    CONNECTION_TIMEOUT_LENGTH = 60
    CUSTOM_HEADERS = Authorization;Basic @Value(_key_encoded)
    ERROR_ATTR = _error
    FOLLOW_REDIRECTS = FOLLOW_WITH_ORIGINAL_METHOD
    HTTP_METHOD = GET
    MAX_HTTP_VERSION = HTTP_2
    MAX_TRANSFERS_IN_PROGRESS = 2
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://scihub.copernicus.eu/dhus/search?q=(footprint:"Intersects(@Value(poly))" AND platformname:$(platform)  AND @Value(product_type) AND @Value(date_param) AND cloudcoverpercentage:[0 TO $(CloudCover)])
    TRANSFER_TIMEOUT_LENGTH = 90
    USE_COOKIES = No
    VERIFY_SSL_CERTIFICATES = Yes
    -> AttributeKeeper
    <REJECTED> -> Junction_5

Bookmark: Spatial filter by Cordinates as Text
AttributeCreator_3
    ATTR_TABLE:
      SET_TO date_param = ingestionDate:[@DateTimeFormat($(BEGIN),%Y-%m-%d)T00:00:00.000Z TO @DateTimeFormat($(END),%Y-%m-%d)T23:59:00.000Z]
      SET_TO wkt_object = @Value(fme_text_string)
      SET_TO product_type = FME_CONDITIONAL:DEFAULT_VALUE'producttype:S2MSI2A'BOOL_OP;OR;COMPOSITE_TEST;<Unused>;TEST $(LEVEL) = Level 1C'producttype:S2MSI1C'FME_NUM_CONDITIONS2___
    -> TestFilter
TestFilter
    DEFAULT_VALUE = <UNFILTERED>
    PASSED_TEST_GROUP_OUTPUT = FIRST
    TEST_LIST = "BOOL_OP,OR,COMPOSITE_TEST,""""""<Unused>"""""",TEST_CLAUSE,CASE_INSENSITIVE_TEST @Value(wkt_object) CONTAINS POINT",Point,"BOOL_OP,OR,COMPOSITE_TEST,""""""<Unused>"""""",TEST_CLAUSE,CASE_INSENSITIVE_TEST @Value(wkt_object) CONTAINS POLYGON",Polygon
    Point -> StringReplacer
    Polygon -> HTTPCaller_5
Note: Select based on intersection with WKT object and platformname:Sentinel-2 and ingestion date
HTTPCaller_5
    CONNECTION_TIMEOUT_LENGTH = 60
    CUSTOM_HEADERS = Authorization;Basic @Value(_key_encoded)
    ERROR_ATTR = _error
    FOLLOW_REDIRECTS = FOLLOW_WITH_ORIGINAL_METHOD
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://scihub.copernicus.eu/dhus/search?q=(footprint:"Intersects(@Value(wkt_object))" AND platformname:$(platform)  AND @Value(product_type) AND @Value(date_param) AND cloudcoverpercentage:[0 TO $(CloudCover)])
    TRANSFER_TIMEOUT_LENGTH = 90
    USE_COOKIES = No
    VERIFY_SSL_CERTIFICATES = Yes
    -> AttributeKeeper
    <REJECTED> -> Junction_5

Bookmark: POINT replacer
StringReplacer
    CASE = NO
    FIND_TEXT = POINT(
    NO_MATCH = _FME_NO_OP_
    REGEXP = NO
    SRC_ATTRS = wkt_object
    -> StringReplacer_2
StringReplacer_2
    CASE = NO
    FIND_TEXT = )
    NO_MATCH = _FME_NO_OP_
    REGEXP = NO
    SRC_ATTRS = wkt_object
    -> HTTPCaller_5

Bookmark: Check online status of requested image
Note: Get information from response_body
XMLFragmenter
    ATTRIBUTE_XML = _response_body
    EMBEDDED_EXPRESSIONS = entry
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = link{0}.href link{1}.href date{3}
    REJECT_FEATURES_WITH_NO_FRAGMENTS = YES
    XML_SOURCE_TYPE = Attribute with XML document
    FRAGMENTS -> Tester_2
    <REJECTED> -> Terminator_2
Note: Only the most recent images?
Tester_2
    BOOL_OP = OR
    TEST_CLAUSE = TEST $(MOST_RECENT) = YES
    TEST_MODE = TEST
    PASSED -> Sorter
    FAILED -> AttributeRenamer
AttributeRenamer
    ATTR_TABLE:
      RENAME_SET_DEFAULT link{0}.href > download_url
      RENAME_SET_DEFAULT link{1}.href > online_status
    MISSING_INPUT_ATTRS = REMOVE
    -> HTTPCaller_6
Note: Use URL from link{1}.href to query for the online status
HTTPCaller_6
    CONNECTION_TIMEOUT_LENGTH = 120
    CUSTOM_HEADERS = Authorization;Basic @Value(_key_encoded)
    ERROR_ATTR = _error
    FOLLOW_REDIRECTS = FOLLOW_WITH_ORIGINAL_METHOD
    HTTP_METHOD = GET
    MAX_HTTP_VERSION = HTTP_2
    MAX_TRANSFERS_IN_PROGRESS = 3
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(online_status)/Online/$value
    TRANSFER_TIMEOUT_LENGTH = 90
    USE_COOKIES = No
    VERIFY_SSL_CERTIFICATES = Yes
    -> Tester_7
    <REJECTED> -> Terminator_3
Note: Data online?
Tester_7
    BOOL_OP = OR
    TEST_CLAUSE = TEST @Value(_response_body) = true
    TEST_MODE = TEST
    PASSED -> Logger_5
    FAILED -> Logger_4
Logger_5
    LOG_FEATURE = NONE
    MAXFEATS = 20
    MESSAGE = Reqeusted data is ONLINE. Download will be triggered now.
    SEVERITY = WARN
    LOGGED -> Junction
    LOGGED -> AttributeKeeper_2
Logger_4
    LOG_FEATURE = NONE
    MAXFEATS = 20
    MESSAGE:
      Reqeusted data is NOT ONLINE. Sentinel's Long Time Archive (LTA) will be triggered now. If successfull, data will be available within hours.
      For further information, see https://scihub.copernicus.eu/userguide/LongTermArchive
    SEVERITY = WARN
    LOGGED -> Junction
    LOGGED -> HTTPCaller_2
Note: Terminate the translation if query fails
Note: Sentinel data is moved to the archive after a certain period. A download request will trigger the data to be "re-uploaded" to the hub.
Terminator_3
    MESSAGE:
      Translation Terminated. Cannot query the online status of the data.
      HTTP Code: @Value(_http_status_code) Error: @Value(fme_rejection_code)
Note: Terminate the translation if no results were acquired
Terminator_2
    MESSAGE:
      Translation Terminated. There are zero search results with your parameters.
      To get results, please change the parameters, e.g. the ingestion date or the maximum cloud coverage percentage.

Bookmark: Get only the most recent image
Sorter
    SORT_PARM = date{3} NUMERIC ASCENDING
    SORTED -> DateTimeConverter
DateTimeConverter
    DATETIME_ATTR = date{3}
    OUT_FORMAT = %Y%m%d
    PASSTHROUGH = NO
    REPAIR_INPUT = YES
    -> StatisticsCalculator_2
StatisticsCalculator_2
    CALCULATION_MODE = NUMERIC
    FEAT_STATS = date{3},NUMERIC_MODE,,MAX,,,,,,,,,,,
    COMPLETE -> Tester_3
Tester_3
    BOOL_OP = OR
    TEST_CLAUSE = TEST @Value(date{3}) = @Value(date{3}.max)
    TEST_MODE = TEST
    PASSED -> AttributeRenamer

Bookmark: SPATIAL RESOLUTION = Specific bands
AttributeKeeper_2
    CREATE_BULK_MODE_FEATURES = NO
    KEEP_ATTRS = _key_encoded,download_url
    -> StringReplacer_3
StringReplacer_3
    CASE = NO
    FIND_TEXT = /$value
    NO_MATCH = _FME_NO_OP_
    REGEXP = NO
    REPLACE_TEXT = /Nodes?$format=json
    SRC_ATTRS = download_url
    -> HTTPCaller_4
Note: Get Nodes endpoint
HTTPCaller_4
    CONNECTION_TIMEOUT_LENGTH = 60
    CUSTOM_HEADERS = Authorization;Basic @Value(_key_encoded)
    ERROR_ATTR = _error
    FOLLOW_REDIRECTS = FOLLOW_WITH_ORIGINAL_METHOD
    HTTP_METHOD = GET
    MAX_HTTP_VERSION = HTTP_2
    MAX_TRANSFERS_IN_PROGRESS = 2
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(download_url)
    TRANSFER_TIMEOUT_LENGTH = 90
    USE_COOKIES = No
    VERIFY_SSL_CERTIFICATES = Yes
    -> JSONFlattener
    <REJECTED> -> Junction_3
JSONFlattener
    ERROR_LIST_ATTR = _json_error
    JSON_DOCUMENT = @Value(_response_body)
    NEW_ATTRIBUTES = d.results{0}.Nodes.__deferred.uri
    READ_FROM_FILE = NO
    RECURSIVE = Yes
    -> AttributeRenamer_2
    <REJECTED> -> Junction_11
AttributeRenamer_2
    ATTR_TABLE = RENAME_SET_DEFAULT d.results{0}.Nodes.__deferred.uri > nodes_url
    MISSING_INPUT_ATTRS = REMOVE
    -> AttributeKeeper_3
AttributeKeeper_3
    CREATE_BULK_MODE_FEATURES = NO
    KEEP_ATTRS = _key_encoded,nodes_url
    -> HTTPCaller_7
Note: Get GRANULE Wrapper
HTTPCaller_7
    CONNECTION_TIMEOUT_LENGTH = 60
    CUSTOM_HEADERS = Authorization;Basic @Value(_key_encoded)
    ERROR_ATTR = _error
    FOLLOW_REDIRECTS = FOLLOW_WITH_ORIGINAL_METHOD
    HTTP_METHOD = GET
    MAX_HTTP_VERSION = HTTP_2
    MAX_TRANSFERS_IN_PROGRESS = 2
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(nodes_url)('GRANULE')/Nodes?$format=json
    TRANSFER_TIMEOUT_LENGTH = 90
    USE_COOKIES = No
    VERIFY_SSL_CERTIFICATES = Yes
    -> JSONFragmenter
    <REJECTED> -> Junction_3
JSONFragmenter
    EXPLODE_FORMAT = JSON
    EXTRACT_ATTR = Yes
    JSON_ATTR = _response_body
    JSON_QUERY = json["d"]["results"][*]
    READ_FROM_FILE = NO
    RECURSIVE = Yes
    REJECT_EMPTY_LISTS = YES
    FRAGMENTS -> AttributeExposer
    <REJECTED> -> Junction_11
AttributeExposer
    ATTR_LIST = __metadata.id
    -> AttributeKeeper_4
AttributeKeeper_4
    CREATE_BULK_MODE_FEATURES = NO
    KEEP_ATTRS = __metadata.id,_key_encoded
    -> HTTPCaller_9
Note: Get IMG_DATA folder
HTTPCaller_9
    CONNECTION_TIMEOUT_LENGTH = 60
    CUSTOM_HEADERS = Authorization;Basic @Value(_key_encoded)
    ERROR_ATTR = _error
    FOLLOW_REDIRECTS = FOLLOW_WITH_ORIGINAL_METHOD
    HTTP_METHOD = GET
    MAX_HTTP_VERSION = HTTP_2
    MAX_TRANSFERS_IN_PROGRESS = 2
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(__metadata.id)/Nodes('IMG_DATA')/Nodes?$format=json
    TRANSFER_TIMEOUT_LENGTH = 90
    USE_COOKIES = No
    VERIFY_SSL_CERTIFICATES = Yes
    -> JSONFragmenter_2
    <REJECTED> -> Junction_4
JSONFragmenter_2
    EXPLODE_FORMAT = JSON
    EXTRACT_ATTR = Yes
    JSON_ATTR = _response_body
    JSON_QUERY = json["d"]["results"][*]
    NEW_ATTRIBUTES = Id
    READ_FROM_FILE = NO
    RECURSIVE = Yes
    REJECT_EMPTY_LISTS = YES
    FRAGMENTS -> Tester_8
    <REJECTED> -> Junction_9
Junction_9
    -> Junction_10
Note: Product level?
Tester_8
    BOOL_OP = OR
    TEST_CLAUSE = TEST $(LEVEL) = Level 2A
    TEST_MODE = TEST
    PASSED -> TestFilter_2
    FAILED -> TestFilter_3
TestFilter_2
    DEFAULT_VALUE = <UNFILTERED>
    PASSED_TEST_GROUP_OUTPUT = FIRST
    TEST_LIST:
      "BOOL_OP,OR,COMPOSITE_TEST,""""""1"""""",TEST_CLAUSE,TEST $(Band_Resolution) = All",All,"BOOL_OP,AND,COMPOSITE_TEST,""""""1 AND 2"""""",TEST_CLAUSE,TEST $(Band_Resolution) = 10m
      TEST @Value(Id) = R10m",10m,"BOOL_OP,AND,COMPOSITE_TEST,""""""1 AND 2"""""",TEST_CLAUSE,TEST $(Band_Resolution) = 20m
      TEST @Value(Id) = R20m",20m,"BOOL_OP,AND,COMPOSITE_TEST,""""""1 AND 2"""""",TEST_CLAUSE,TEST $(Band_Resolution) = 60m
      TEST @Value(Id) = R60m",60m
    All -> AttributeCreator_5
    10m -> AttributeCreator_5
    20m -> AttributeCreator_5
    60m -> AttributeCreator_5
AttributeCreator_5
    ATTR_TABLE = SET_TO image_identifier = @Value(__metadata.id)/Nodes
    -> HTTPCaller_8
Note: Download data
HTTPCaller_8
    CONNECTION_TIMEOUT_LENGTH = 60
    CUSTOM_HEADERS = Authorization;Basic @Value(_key_encoded)
    ERROR_ATTR = _error
    FOLLOW_REDIRECTS = FOLLOW_WITH_ORIGINAL_METHOD
    HTTP_METHOD = GET
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    RETRY_FAILED_TRANSFERS = CONNECTION 429 500 501 502 503 504 505 506 507 508 509 510 511
    RETRY_INITIAL_BACKOFF = 500
    RETRY_MAX_RETRIES = 3
    SPLIT_MULTIPART_DOWNLOADS = NO
    STATUS_CODE_ATTR = _http_status_code
    TARGET_ATTR = _response_body
    TARGET_ATTR_ENCODING = auto-detect
    TARGET_URL = @Value(image_identifier)?$format=json
    TRANSFER_TIMEOUT_LENGTH = 90
    USE_COOKIES = No
    VERIFY_SSL_CERTIFICATES = Yes
    -> JSONFragmenter_3
    <REJECTED> -> Junction_2
JSONFragmenter_3
    EXPLODE_FORMAT = JSON
    EXTRACT_ATTR = Yes
    JSON_ATTR = _response_body
    JSON_QUERY = json["d"]["results"][*]
    NEW_ATTRIBUTES = Id
    READ_FROM_FILE = NO
    RECURSIVE = Yes
    REJECT_EMPTY_LISTS = YES
    FRAGMENTS -> Tester_4
    <REJECTED> -> Junction_7
Tester_4
    BOOL_OP = COMPOSITE
    COMPOSITE_TEST = 1 AND 2
    TEST_CLAUSE:
      CASE_INSENSITIVE_TEST @Value(Id) NOT_CONTAINS _AOT_
      CASE_INSENSITIVE_TEST @Value(Id) NOT_CONTAINS _WVP_
    TEST_MODE = CASE_INSENSITIVE_TEST
    PASSED -> AttributeCreator_6
Junction_7
    -> Junction_8
TestFilter_3
    DEFAULT_VALUE = <UNFILTERED>
    PASSED_TEST_GROUP_OUTPUT = FIRST
    TEST_LIST:
      "BOOL_OP,OR,COMPOSITE_TEST,""""""1"""""",TEST_CLAUSE,TEST $(Band_Resolution) = All",All,"BOOL_OP,COMPOSITE,COMPOSITE_TEST,""""""1 AND ( 2 OR 3 OR 4 OR 5 )"""""",TEST_CLAUSE,TEST $(Band_Resolution) = 10m
      CASE_INSENSITIVE_TEST @Value(Id) CONTAINS _B02.jp2
      CASE_INSENSITIVE_TEST @Value(Id) CONTAINS _B03.jp2
      CASE_INSENSITIVE_TEST @Value(Id) CONTAINS _B04.jp2
      CASE_INSENSITIVE_TEST @Value(Id) CONTAINS _B08.jp2",10m,"BOOL_OP,COMPOSITE,COMPOSITE_TEST,""""""1 AND ( 2 OR 3 OR 4 OR 5 OR 6 OR 7 )"""""",TEST_CLAUSE,TEST $(Band_Resolution) = 20m
      CASE_INSENSITIVE_TEST @Value(Id) CONTAINS _B05.jp2
      CASE_INSENSITIVE_TEST @Value(Id) CONTAINS _B06.jp2
      CASE_INSENSITIVE_TEST @Value(Id) CONTAINS _B07.jp2
      CASE_INSENSITIVE_TEST @Value(Id) CONTAINS _B8A.jp2
      CASE_INSENSITIVE_TEST @Value(Id) CONTAINS _B11.jp2
      CASE_INSENSITIVE_TEST @Value(Id) CONTAINS _B12.jp2",20m,"BOOL_OP,COMPOSITE,COMPOSITE_TEST,""""""1 AND ( 2 OR 3 OR 4 )"""""",TEST_CLAUSE,TEST $(Band_Resolution) = 60m
      CASE_INSENSITIVE_TEST @Value(Id) CONTAINS _B01.jp2
      CASE_INSENSITIVE_TEST @Value(Id) CONTAINS _B09.jp2
      CASE_INSENSITIVE_TEST @Value(Id) CONTAINS _B10.jp2",60m
    20m -> AttributeCreator_6
AttributeCreator_6
    ATTR_TABLE = SET_TO image_download_url = @Value(__metadata.id)/$value
    -> AttributeKeeper_5
AttributeKeeper_5
    CREATE_BULK_MODE_FEATURES = NO
    KEEP_ATTRS = image_download_url,Id,_key_encoded
    -> HTTPCaller_10
Note: Download data
HTTPCaller_10
    CONNECTION_TIMEOUT_LENGTH = 60
    CUSTOM_HEADERS = Authorization;Basic @Value(_key_encoded)
    ERROR_ATTR = _error
    FILE_PATH_ATTR = _response_file_path
    FOLLOW_REDIRECTS = FOLLOW_WITH_ORIGINAL_METHOD
    HTTP_METHOD = GET
    MAX_HTTP_VERSION = HTTP_2
    MAX_TRANSFERS_IN_PROGRESS = 2
    MINIMUM_ENCRYPTION_LEVEL = OS_DEFAULT
    OUTPUT_FILENAME = @Value(Id)
    REDIRECT_AUTH = ORIGINAL_DOMAIN_ONLY
    RESPONSE_TYPE = File
    STATUS_CODE_ATTR = _http_status_code
    TARGET_URL = @Value(image_download_url)
    TRANSFER_TIMEOUT_LENGTH = 90
    USE_COOKIES = No
    VERIFY_SSL_CERTIFICATES = Yes
    -> FeatureReader_2 [INITIATOR]
    <REJECTED> -> Junction_2
Junction_11
    -> Junction_12
Junction_12
    -> Junction_13
Junction
    -> XMLFragmenter_2

Bookmark: Error catching
Junction_10
    -> Junction_6
Junction_8
    -> Junction_6
Junction_2
    -> FeatureHolder
FeatureHolder
    -> AttributeManager
AttributeManager
    ATTR_TABLE:
      REMOVE image_download_url
      REMOVE _key_encoded
      REMOVE Id
      REMOVE _response_file_path
      REMOVE nodes_url
      REMOVE date_param
      REMOVE poly
      REMOVE product_type
      REMOVE coord{}.x
      REMOVE coord{}.y
      REMOVE coord{}.z
      REMOVE wkt_object
      REMOVE fme_text_string
      REMOVE fme_rotation
      REMOVE fme_text_size
      REMOVE _x
      REMOVE _y
      REMOVE _z
      REMOVE download_url
      REMOVE __metadata.id
      REMOVE image_identifier
      REMOVE json_type
      REMOVE json_index
    -> Terminator_4
Terminator_4
    MESSAGE:
      Error at requesting the REST API.
      HTTP Code: @Value(_http_status_code)
      Error: @Value(_error)
Junction_13
    -> Junction_6
Junction_6
    -> FeatureHolder_2
FeatureHolder_2
    -> AttributeManager_2
AttributeManager_2
    ATTR_TABLE:
      REMOVE _key_encoded
      REMOVE __metadata.id
      REMOVE _response_body
      REMOVE _http_status_code
      REMOVE download_url
      REMOVE d.results{0}.Nodes.__deferred.uri
      REMOVE nodes_url
      REMOVE image_identifier
      REMOVE json_type
      REMOVE json_index
      REMOVE Id
      REMOVE d.results{}.Nodes.__deferred.uri
    -> Terminator_5
Terminator_5
    MESSAGE:
      Error at parsing the response JSON.
      Error: @Value(_json_error{0}.message)
      FME rejection code: @Value(fme_rejection_code)

Bookmark: Read in Sentinel-Images
FeatureReader_2
    ATTRIBUTES = JPEG2000,fme_basename
    ATTR_ACCUM_MODE = Only Use Result
    COMBINE_GEOM = Use Result
    DATASET = @Value(_response_file_path)
    FEATURETYPES = JPEG2000
    FORMAT = JPEG2000
    INTERACT = NONE
    JPEG2000_COMPRESSION_CACHE_SIZE_CALCULATION = AUTO
    JPEG2000_GROUP_BY_DATASET = No
    JPEG2000_JPEG2000_EXPOSE_FORMAT_ATTRS = fme_basename,char(50)
    JPEG2000_PREFER_FILE_CS_UNITS = Yes
    JPEG2000_READER_META_ATTRIBUTES = fme_dataset fme_basename
    JPEG2000_READ_OFFSETS_IN_CS_UNITS = No
    JPEG2000_USE_SEARCH_ENVELOPE = NO
    OUTPUT_FEATURES_DISPLAY = Schema and Data Features
    JPEG2000 -> TestFilter_4
TestFilter_4
    DEFAULT_VALUE = <UNFILTERED>
    PASSED_TEST_GROUP_OUTPUT = FIRST
    TEST_LIST = "BOOL_OP,OR,COMPOSITE_TEST,""""""1"""""",TEST_CLAUSE,CASE_SENSITIVE_TEST @Value(fme_basename) CONTAINS_REGEX B01",B01,"BOOL_OP,OR,COMPOSITE_TEST,""""""1"""""",TEST_CLAUSE,CASE_SENSITIVE_TEST @Value(fme_basename) CONTAINS_REGEX B02",B02,"BOOL_OP,OR,COMPOSITE_TEST,""""""1"""""",TEST_CLAUSE,CASE_SENSITIVE_TEST @Value(fme_basename) CONTAINS_REGEX B03",B03,"BOOL_OP,OR,COMPOSITE_TEST,""""""1"""""",TEST_CLAUSE,CASE_SENSITIVE_TEST @Value(fme_basename) CONTAINS_REGEX B04",B04,"BOOL_OP,OR,COMPOSITE_TEST,""""""1"""""",TEST_CLAUSE,CASE_SENSITIVE_TEST @Value(fme_basename) CONTAINS_REGEX B05",B05,"BOOL_OP,OR,COMPOSITE_TEST,""""""1"""""",TEST_CLAUSE,CASE_SENSITIVE_TEST @Value(fme_basename) CONTAINS_REGEX B06",B06,"BOOL_OP,OR,COMPOSITE_TEST,""""""1"""""",TEST_CLAUSE,CASE_SENSITIVE_TEST @Value(fme_basename) CONTAINS_REGEX B07",B07,"BOOL_OP,OR,COMPOSITE_TEST,""""""1"""""",TEST_CLAUSE,CASE_SENSITIVE_TEST @Value(fme_basename) CONTAINS_REGEX B08",B08,"BOOL_OP,OR,COMPOSITE_TEST,""""""1"""""",TEST_CLAUSE,CASE_SENSITIVE_TEST @Value(fme_basename) CONTAINS_REGEX B8A",B8A,"BOOL_OP,OR,COMPOSITE_TEST,""""""1"""""",TEST_CLAUSE,CASE_SENSITIVE_TEST @Value(fme_basename) CONTAINS_REGEX B09",B09,"BOOL_OP,OR,COMPOSITE_TEST,""""""1"""""",TEST_CLAUSE,CASE_SENSITIVE_TEST @Value(fme_basename) CONTAINS_REGEX B10",B10,"BOOL_OP,OR,COMPOSITE_TEST,""""""1"""""",TEST_CLAUSE,CASE_SENSITIVE_TEST @Value(fme_basename) CONTAINS_REGEX B11",B11,"BOOL_OP,OR,COMPOSITE_TEST,""""""1"""""",TEST_CLAUSE,CASE_SENSITIVE_TEST @Value(fme_basename) CONTAINS_REGEX B12",B12,"BOOL_OP,OR,COMPOSITE_TEST,""""""1"""""",TEST_CLAUSE,CASE_SENSITIVE_TEST @Value(fme_basename) CONTAINS_REGEX TCI",TCI
    B01 -> B01 (output)
    B02 -> B02 (output)
    B03 -> B03 (output)
    B04 -> B04 (output)
    B05 -> B05 (output)
    B06 -> B06 (output)
    B07 -> B07 (output)
    B08 -> B08 (output)
    B8A -> B8A (output)
    B09 -> B09 (output)
    B10 -> B10 (output)
    B11 -> B11 (output)
    B12 -> B12 (output)
    TCI -> TCI (output)
B01 (output)
B02 (output)
B03 (output)
B04 (output)
B05 (output)
B06 (output)
B07 (output)
B08 (output)
B8A (output)
B09 (output)
B10 (output)
B11 (output)
B12 (output)
TCI (output)

Bookmark: Write information to log file
XMLFragmenter_2
    ATTRIBUTE_XML = xml_fragment
    EMBEDDED_EXPRESSIONS = date[@name="ingestiondate"]
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = date
    REJECT_FEATURES_WITH_NO_FRAGMENTS = YES
    XML_SOURCE_TYPE = Attribute with XML document
    FRAGMENTS -> StatisticsCalculator
StatisticsCalculator
    CALCULATION_MODE = NUMERIC
    FEAT_STATS = xml_matched_element,NUMERIC_MODE,,,COUNT,,,,,,,,,,
    PREPEND_ATTR_NAME_OBS = No
    STATISTIC_SUFFIX_RENAME_MAP = COUNT,_count
    SUMMARY -> FeatureMerger [REQUESTOR]
    COMPLETE -> ListBuilder
ListBuilder
    LIST_ATTRS_TO_INCLUDE = date
    LIST_NAME = _datelist
    -> ListConcatenator
ListConcatenator
    DROP_EMPTY_PARTS = No
    LIST_ATTR = _datelist{}.date
    SEP = " & "
    VAL_ATTR = _concatenated
    -> FeatureMerger [SUPPLIER]
FeatureMerger
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = 1 1 AUTO
    MERGE_TYPE = Attributes Only
    PROCESS_DUPS = YES
    REJECT_NULL_MISSING_KEYS = No
    SUPPLIERS_FIRST = No
    MERGED -> Logger
Logger
    LOG_FEATURE = NONE
    MAXFEATS = 100
    MESSAGE:
      Your request delivers @Value(_count) result(s).
      The request delivers images at the following dates: @Value(_concatenated)
    SEVERITY = WARN

Bookmark: Messaging in log file for retrieving of offline data
Note: Trigger ex-archiving
HTTPCaller_2
    CONNECTION_TIMEOUT_LENGTH = 60
    CUSTOM_HEADERS = Authorization;Basic @Value(_key_encoded)
    ERROR_ATTR = _error
    FOLLOW_REDIRECTS = FOLLOW_WITH_ORIGINAL_METHOD
    HTTP_METHOD = GET
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = @Value(download_url)
    TRANSFER_TIMEOUT_LENGTH = 90
    USE_COOKIES = No
    VERIFY_SSL_CERTIFICATES = Yes
    -> Tester
Tester
    BOOL_OP = OR
    TEST_CLAUSE = TEST @Value(_http_status_code) = 202
    TEST_MODE = TEST
    PASSED -> Logger_2
    FAILED -> AttributeCreator_4
Logger_2
    LOG_FEATURE = NONE
    MAXFEATS = 20
    MESSAGE = Retrieval of offline data is triggered successfully. Please try again in a few hours.
    SEVERITY = WARN
AttributeCreator_4
    ATTR_TABLE = SET_TO error_msg = FME_CONDITIONAL:DEFAULT_VALUE'_FME_NO_OP_'BOOL_OP;OR;COMPOSITE_TEST;1;TEST @Value(_http_status_code) = 503'Service unavailable. LTA cannot accept new requests right now. Try again soon.'BOOL_OP;OR;COMPOSITE_TEST;1;TEST @Value(_http_status_code) = 403'Request forbidden. Number of submissions exceeds allowed user quota.'BOOL_OP;OR;COMPOSITE_TEST;1;TEST @Value(_http_status_code) = 500'Internal server error.'FME_NUM_CONDITIONS4___
    -> Logger_3
Logger_3
    LOG_FEATURE = NONE
    MAXFEATS = 20
    MESSAGE = @Value(error_msg)
    SEVERITY = ERROR
